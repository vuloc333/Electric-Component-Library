(defun ShowCBL_Core (/ ss i ent obj familyFound atts tagStr)
  (vl-load-com)
  (setq ss (ssget "_X" '((0 . "INSERT"))))
  (if ss
    (progn
      (setq i 0)
      (repeat (sslength ss)
        (setq ent (ssname ss i))
        (setq obj (vlax-ename->vla-object ent))
        (setq familyFound nil)
        (setq atts (vlax-invoke obj 'GetAttributes))
        (foreach att atts
          (if (and (= (strcase (vla-get-TagString att)) "FAMILY")
                   (= (strcase (vla-get-TextString att)) "CBL"))
            (setq familyFound t)
          )
        )
        (if (= familyFound t)
          (foreach att atts
            (setq tagStr (strcase (vla-get-TagString att)))
            (if (or (wcmatch tagStr "TAG*") (= tagStr "DESC1"))
              (vla-put-Invisible att :vlax-false)
            )
          )
        )
        (setq i (1+ i))
      )
    )
  )
)
; Execute the function immediately
(ShowCBL_Core)
